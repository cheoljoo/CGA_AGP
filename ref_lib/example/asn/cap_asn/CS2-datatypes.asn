-------------------------------------------------------------------
-- Subset of CS2-datatypes module needed to compile CAP
-------------------------------------------------------------------
--ETSI EN 301 140-5 V1.1.3 (1999-11)
--European Standard (Telecommunications series)
--Intelligent Network (IN);
--Intelligent Network Application Protocol (INAP);
--Capability Set 2 (CS2);
--Part 5: Distributed Functional Plane (DFP)
-------------------------------------------------------------------

CS2-datatypes DEFINITIONS IMPLICIT TAGS ::=
BEGIN
IMPORTS
	MiscCallInfo
FROM CS1-datatypes;

BothwayThroughConnectionInd ::= ENUMERATED {
  bothwayPathRequired(0), bothwayPathNotRequired(1)}

CriticalityType ::= ENUMERATED {ignore(0), abort(1)}

--MiscCallInfo ::= SEQUENCE {
--  messageType  [0]  ENUMERATED {request(0), notification(1), ...}
--}

END
